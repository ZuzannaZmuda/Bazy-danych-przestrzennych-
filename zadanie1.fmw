FME workspace zadanie1.fmw

Parameters:
- SourceDataset_SHAPEFILE = ""/Users/zuziak/Desktop/AGH/Semestr 5 AGH/Bazy Danych Przestrzennych/dane2/T2019_KAR_POI_TABLE.shp" "/Users/zuziak/Desktop/AGH/Semestr 5 AGH/Bazy Danych Przestrzennych/dane2/T2019_KAR_STREET_NODE.shp" "/Users/zuziak/Desktop/AGH/Semestr 5 AGH/Bazy Danych Przestrzennych/dane2/T2019_KAR_STREETS.shp""   # Source Esri Shapefile(s)
- SourceDataset_CSV2 = /Users/zuziak/Downloads/routePoints.csv   # Source CSV (Comma Separated Value) File(s)
- SourceDataset_SHAPEFILE_17 = /Users/zuziak/Desktop/AGH/Semestr 5 AGH/Bazy Danych Przestrzennych/dane2/T2019_KAR_STREETS.shp   # Source Esri Shapefile(s)
- FEATURE_TYPES =
- SourceDataset_CSV2_9 = /Users/zuziak/Downloads/routePoints.csv   # Source CSV (Comma Separated Value) File(s)
- FEATURE_TYPES_2 =
- SourceDataset_CSV2_13 = /Users/zuziak/Downloads/routePoints.csv   # Source CSV (Comma Separated Value) File(s)
- FEATURE_TYPES_3 =
- SourceDataset_SHAPEFILE_13 = ""/Users/zuziak/Desktop/AGH/Semestr 5 AGH/Bazy Danych Przestrzennych/dane2/T2019_KAR_STREET_NODE.shp" "/Users/zuziak/Desktop/AGH/Semestr 5 AGH/Bazy Danych Przestrzennych/dane2/T2019_KAR_STREETS.shp" "/Users/zuziak/Desktop/AGH/Semestr 5 AGH/Bazy Danych Przestrzennych/dane2/T2019_KAR_POI_TABLE.shp""   # Source Esri Shapefile(s)
- SourceDataset_CSV2_11 = /Users/zuziak/Downloads/routePoints.csv   # Source CSV (Comma Separated Value) File(s)
- SourceDataset_CSV2_8 = /Users/zuziak/Downloads/routePoints.csv   # Source CSV (Comma Separated Value) File(s)
- SourceDataset_SHAPEFILE_21 = /Users/zuziak/Desktop/AGH/Semestr 5 AGH/Bazy Danych Przestrzennych/dane2/T2019_KAR_STREETS.shp   # Source Esri Shapefile(s)
- SourceDataset_SHAPEFILE_15 = /Users/zuziak/Desktop/AGH/Semestr 5 AGH/Bazy Danych Przestrzennych/dane2/T2019_KAR_STREETS.shp   # Source Esri Shapefile(s)
- SourceDataset_SHAPEFILE_19 = /Users/zuziak/Desktop/AGH/Semestr 5 AGH/Bazy Danych Przestrzennych/dane2/T2019_KAR_POI_TABLE.shp   # Source Esri Shapefile(s)
- SourceDataset_SHAPEFILE_12 = /Users/zuziak/Desktop/AGH/Semestr 5 AGH/Bazy Danych Przestrzennych/dane2/T2019_KAR_POI_TABLE.shp   # Source Esri Shapefile(s)
- SourceDataset_SHAPEFILE_14 = /Users/zuziak/Desktop/AGH/Semestr 5 AGH/Bazy Danych Przestrzennych/dane2/T2019_KAR_STREETS.shp   # Source Esri Shapefile(s)
- SourceDataset_SHAPEFILE_16 = /Users/zuziak/Desktop/AGH/Semestr 5 AGH/Bazy Danych Przestrzennych/dane2/T2019_KAR_STREETS.shp   # Source Esri Shapefile(s)
- SourceDataset_CSV2_10 = /Users/zuziak/Downloads/routePoints.csv   # Source CSV (Comma Separated Value) File(s)
- SourceDataset_CSV2_12 = /Users/zuziak/Downloads/routePoints.csv   # Source CSV (Comma Separated Value) File(s)
- SourceDataset_SHAPEFILE_18 = /Users/zuziak/Desktop/AGH/Semestr 5 AGH/Bazy Danych Przestrzennych/dane2/T2019_KAR_STREET_NODE.shp   # Source Esri Shapefile(s)
- SourceDataset_SHAPEFILE_20 = /Users/zuziak/Desktop/AGH/Semestr 5 AGH/Bazy Danych Przestrzennych/dane2/T2019_KAR_STREET_NODE.shp   # Source Esri Shapefile(s)

Readers:
- SHAPEFILE_1: SHAPEFILE from $(SourceDataset_SHAPEFILE)
- CSV2_1: CSV2 from $(SourceDataset_CSV2)
- SHAPEFILE_2: SHAPEFILE from $(SourceDataset_SHAPEFILE_17)
- CSV2_2: CSV2 from $(SourceDataset_CSV2_9)
- CSV2_3: CSV2 from $(SourceDataset_CSV2_13)
- SHAPEFILE_3: SHAPEFILE from $(SourceDataset_SHAPEFILE_13)
- CSV2_4: CSV2 from $(SourceDataset_CSV2_11)
- CSV2_5: CSV2 from $(SourceDataset_CSV2_8)
- SHAPEFILE_4: SHAPEFILE from $(SourceDataset_SHAPEFILE_21)
- SHAPEFILE_5: SHAPEFILE from $(SourceDataset_SHAPEFILE_15)
- SHAPEFILE_6: SHAPEFILE from $(SourceDataset_SHAPEFILE_19)
- SHAPEFILE_7: SHAPEFILE from $(SourceDataset_SHAPEFILE_12)
- SHAPEFILE_8: SHAPEFILE from $(SourceDataset_SHAPEFILE_14)
- SHAPEFILE_9: SHAPEFILE from $(SourceDataset_SHAPEFILE_16)
- CSV2_6: CSV2 from $(SourceDataset_CSV2_10)
- CSV2_7: CSV2 from $(SourceDataset_CSV2_12)
- SHAPEFILE_10: SHAPEFILE from $(SourceDataset_SHAPEFILE_18)
- SHAPEFILE_11: SHAPEFILE from $(SourceDataset_SHAPEFILE_20)

Note: Zadanie 5b
T2019_KAR_STREETS (reader SHAPEFILE_1)
    attributes: LINK_ID long, ST_NAME varchar(254), REF_IN_ID long, NREF_IN_ID long, FUNC_CLASS varchar(1), SPEED_CAT varchar(1), FR_SPEED_L long, TO_SPEED_L long, DIR_TRAVEL varchar(1)
    -> T2019_KAR_STREETS
    -> Reprojector_4
T2019_KAR_STREETS: Inspector
Reprojector_4
    DEST = DHDN.Berlin/Cassini
    INTERPOLATION_TYPE_NAME = Nearest Neighbor
    RASTER_CELL_SIZE = Preserve Cells
    RASTER_TOLERANCE = 0.0
    SOURCE = $(SourceDataset_SHAPEFILE)
    REPROJECTED -> Tester
Tester
    BOOL_OP = OR
    TEST_CLAUSE:
      TEST @Value(DIR_TRAVEL) = B
      TEST @Value(DIR_TRAVEL) = T
    TEST_MODE = TEST
    PASSED -> AttributeCreator
    FAILED -> AttributeCreator_2
AttributeCreator
    ATTR_TABLE:
      SET_TO ForwardCost = 1
      SET_TO ReverseCost = 1
    -> ShortestPathFinder [NETWORK]
AttributeCreator_2
    ATTR_TABLE:
      SET_TO ForwardCost = 1
      SET_TO ReverseCost = 9999
    -> ShortestPathFinder [NETWORK]
Note: Zadanie 6b
CSV (reader CSV2_4)
    attributes: x x_coordinate, y y_coordinate
    -> VertexCreator_4
VertexCreator_4
    CLOSE_LINES = Yes
    IGNORE_DUPLICATES = No
    MEASURE_TYPE = Continuous
    MISSING_VAL_MODE = Compute
    MODE_NAME = Add Point
    XVAL = @Value(x)
    YVAL = @Value(y)
    -> LineBuilder_4
LineBuilder_4
    ACCUM_INPUT_ATTRS = Use Attributes From One Feature
    REMOVE_DUPLICATES = NO
    LINE -> Reprojector_3
Reprojector_3
    DEST = DHDN.Berlin/Cassini
    INTERPOLATION_TYPE_NAME = Nearest Neighbor
    RASTER_CELL_SIZE = Preserve Cells
    RASTER_TOLERANCE = 0.0
    REPROJECTED -> ShortestPathFinder_4 [FROM-TO]
CSV (reader CSV2_1)
    attributes: x x_coordinate, y y_coordinate
    -> VertexCreator
VertexCreator
    CLOSE_LINES = Yes
    IGNORE_DUPLICATES = No
    MEASURE_TYPE = Continuous
    MISSING_VAL_MODE = Compute
    MODE_NAME = Add Point
    XVAL = @Value(x)
    YVAL = @Value(y)
    -> LineBuilder
LineBuilder
    ACCUM_INPUT_ATTRS = Use Attributes From One Feature
    REMOVE_DUPLICATES = NO
    LINE -> Reprojector_2
Reprojector_2
    DEST = DHDN.Berlin/Cassini
    INTERPOLATION_TYPE_NAME = Nearest Neighbor
    RASTER_CELL_SIZE = Preserve Cells
    RASTER_TOLERANCE = 0.0
    REPROJECTED -> ShortestPathFinder_3 [FROM-TO]
Note: Zadanie 1 + 4
T2019_KAR_POI_TABLE (reader SHAPEFILE_3)
    attributes: POI_ID long, LINK_ID long, TYPE varchar(250), POI_NAME varchar(250), ST_NAME varchar(250), LAT number(31,15), LON number(31,15)
    -> Reprojector_7
Reprojector_7
    DEST = DHDN.Berlin/Cassini
    INTERPOLATION_TYPE_NAME = Nearest Neighbor
    RASTER_CELL_SIZE = Preserve Cells
    RASTER_TOLERANCE = 0.0
    SOURCE = $(SourceDataset_SHAPEFILE)
T2019_KAR_STREET_NODE (reader SHAPEFILE_3)
    attributes: NODE_ID long, LINK_ID long, POINT_NUM long, Z_LEVEL long, INTERSECT varchar(1), LAT number(31,15), LON number(31,15)
    -> Reprojector_8
Reprojector_8
    DEST = DHDN.Berlin/Cassini
    INTERPOLATION_TYPE_NAME = Nearest Neighbor
    RASTER_CELL_SIZE = Preserve Cells
    RASTER_TOLERANCE = 0.0
    SOURCE = $(SourceDataset_SHAPEFILE)
Note: Zadanie 2,3,4
T2019_KAR_STREETS (reader SHAPEFILE_3)
    attributes: LINK_ID long, ST_NAME varchar(254), REF_IN_ID long, NREF_IN_ID long, FUNC_CLASS varchar(1), SPEED_CAT varchar(1), FR_SPEED_L long, TO_SPEED_L long, DIR_TRAVEL varchar(1)
    -> Reprojector_9
Reprojector_9
    DEST = DHDN.Berlin/Cassini
    INTERPOLATION_TYPE_NAME = Nearest Neighbor
    RASTER_CELL_SIZE = Preserve Cells
    RASTER_TOLERANCE = 0.0
    SOURCE = $(SourceDataset_SHAPEFILE)
Note: Zadanie 5a
CSV (reader CSV2_3)
    attributes: x x_coordinate, y y_coordinate
    -> VertexCreator_3
VertexCreator_3
    CLOSE_LINES = Yes
    IGNORE_DUPLICATES = No
    MEASURE_TYPE = Continuous
    MISSING_VAL_MODE = Compute
    MODE_NAME = Add Point
    XVAL = @Value(x)
    YVAL = @Value(y)
    -> LineBuilder_3
LineBuilder_3
    ACCUM_INPUT_ATTRS = Use Attributes From One Feature
    REMOVE_DUPLICATES = NO
    LINE -> Reprojector_10
Reprojector_10
    DEST = DHDN.Berlin/Cassini
    INTERPOLATION_TYPE_NAME = Nearest Neighbor
    RASTER_CELL_SIZE = Preserve Cells
    RASTER_TOLERANCE = 0.0
Note: Zadanie 6a
T2019_KAR_STREETS (reader SHAPEFILE_5)
    attributes: LINK_ID long, ST_NAME varchar(254), REF_IN_ID long, NREF_IN_ID long, FUNC_CLASS varchar(1), SPEED_CAT varchar(1), FR_SPEED_L long, TO_SPEED_L long, DIR_TRAVEL varchar(1)
    -> Reprojector_13
Reprojector_13
    DEST = DHDN.Berlin/Cassini
    INTERPOLATION_TYPE_NAME = Nearest Neighbor
    RASTER_CELL_SIZE = Preserve Cells
    RASTER_TOLERANCE = 0.0
    SOURCE = $(SourceDataset_SHAPEFILE)
    REPROJECTED -> ShortestPathFinder_4 [NETWORK]
ShortestPathFinder_4
    ALLOW_UTURNS = Yes
    REORDER_MODE = NONE
    SNAP_POINTS = Yes
    SNAP_TOLERANCE = 200
    WEIGHT_ATTR_CHOICE = BY_LENGTH
    PATH -> Bufferer
Bufferer
    ANGLE = 22.5
    CAP_STYLE = Arc
    CORNER_STYLE = Arc
    MODE = AREA
    OFFSET = 5
    OFFSET_UNITS = METERS
    PRECISION = APPROX
    BUFFERED -> SpatialFilter [Filter]
CSV (reader CSV2_5)
    attributes: x x_coordinate, y y_coordinate
    -> VertexCreator_5
VertexCreator_5
    CLOSE_LINES = Yes
    IGNORE_DUPLICATES = No
    MEASURE_TYPE = Continuous
    MISSING_VAL_MODE = Compute
    MODE_NAME = Add Point
    XVAL = @Value(x)
    YVAL = @Value(y)
    -> LineBuilder_5
LineBuilder_5
    ACCUM_INPUT_ATTRS = Use Attributes From One Feature
    REMOVE_DUPLICATES = NO
    LINE -> Reprojector_12
Reprojector_12
    DEST = DHDN.Berlin/Cassini
    INTERPOLATION_TYPE_NAME = Nearest Neighbor
    RASTER_CELL_SIZE = Preserve Cells
    RASTER_TOLERANCE = 0.0
    REPROJECTED -> ShortestPathFinder_2 [FROM-TO]
T2019_KAR_STREETS (reader SHAPEFILE_4)
    attributes: LINK_ID long, ST_NAME varchar(254), REF_IN_ID long, NREF_IN_ID long, FUNC_CLASS varchar(1), SPEED_CAT varchar(1), FR_SPEED_L long, TO_SPEED_L long, DIR_TRAVEL varchar(1)
    -> Reprojector_11
Reprojector_11
    DEST = DHDN.Berlin/Cassini
    INTERPOLATION_TYPE_NAME = Nearest Neighbor
    RASTER_CELL_SIZE = Preserve Cells
    RASTER_TOLERANCE = 0.0
    SOURCE = $(SourceDataset_SHAPEFILE)
    REPROJECTED -> Tester_2
Tester_2
    BOOL_OP = OR
    TEST_CLAUSE:
      TEST @Value(DIR_TRAVEL) = B
      TEST @Value(DIR_TRAVEL) = T
    TEST_MODE = TEST
    PASSED -> AttributeCreator_3
    FAILED -> AttributeCreator_4
AttributeCreator_3
    ATTR_TABLE:
      SET_TO ForwardCost = 1
      SET_TO ReverseCost = 1
    -> ShortestPathFinder_2 [NETWORK]
AttributeCreator_4
    ATTR_TABLE:
      SET_TO ForwardCost = 1
      SET_TO ReverseCost = 9999
    -> ShortestPathFinder_2 [NETWORK]
ShortestPathFinder_2
    ALLOW_UTURNS = Yes
    REORDER_MODE = NONE
    SNAP_POINTS = No
    WEIGHT_ATTR_1 = ForwardCost
    WEIGHT_ATTR_2 = ReverseCost
    WEIGHT_ATTR_CHOICE = BY_TWO_ATTRIBUTES
    PATH -> Bufferer_2
Bufferer_2
    ANGLE = 22.5
    CAP_STYLE = Arc
    CORNER_STYLE = Arc
    MODE = AREA
    OFFSET = 5
    OFFSET_UNITS = METERS
    PRECISION = APPROX
    BUFFERED -> SpatialFilter_2 [Filter]
T2019_KAR_STREETS (reader SHAPEFILE_2)
    attributes: LINK_ID long, ST_NAME varchar(254), REF_IN_ID long, NREF_IN_ID long, FUNC_CLASS varchar(1), SPEED_CAT varchar(1), FR_SPEED_L long, TO_SPEED_L long, DIR_TRAVEL varchar(1)
    -> Reprojector_5
Reprojector_5
    DEST = DHDN.Berlin/Cassini
    INTERPOLATION_TYPE_NAME = Nearest Neighbor
    RASTER_CELL_SIZE = Preserve Cells
    RASTER_TOLERANCE = 0.0
    SOURCE = $(SourceDataset_SHAPEFILE)
    REPROJECTED -> ShortestPathFinder_3 [NETWORK]
ShortestPathFinder_3
    ALLOW_UTURNS = Yes
    REORDER_MODE = NONE
    SNAP_POINTS = Yes
    SNAP_TOLERANCE = 200
    WEIGHT_ATTR_CHOICE = BY_LENGTH
    PATH -> Inspector_2
Inspector_2
CSV (reader CSV2_2)
    attributes: x x_coordinate, y y_coordinate
    -> VertexCreator_2
VertexCreator_2
    CLOSE_LINES = Yes
    IGNORE_DUPLICATES = No
    MEASURE_TYPE = Continuous
    MISSING_VAL_MODE = Compute
    MODE_NAME = Add Point
    XVAL = @Value(x)
    YVAL = @Value(y)
    -> LineBuilder_2
LineBuilder_2
    ACCUM_INPUT_ATTRS = Use Attributes From One Feature
    REMOVE_DUPLICATES = NO
    LINE -> Reprojector_6
Reprojector_6
    DEST = DHDN.Berlin/Cassini
    INTERPOLATION_TYPE_NAME = Nearest Neighbor
    RASTER_CELL_SIZE = Preserve Cells
    RASTER_TOLERANCE = 0.0
    REPROJECTED -> ShortestPathFinder [FROM-TO]
ShortestPathFinder
    ALLOW_UTURNS = Yes
    REORDER_MODE = NONE
    SNAP_POINTS = No
    WEIGHT_ATTR_1 = ForwardCost
    WEIGHT_ATTR_2 = ReverseCost
    WEIGHT_ATTR_CHOICE = BY_TWO_ATTRIBUTES
T2019_KAR_POI_TABLE (reader SHAPEFILE_6)
    attributes: POI_ID long, LINK_ID long, TYPE varchar(250), POI_NAME varchar(250), ST_NAME varchar(250), LAT number(31,15), LON number(31,15)
    -> SpatialFilter [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
T2019_KAR_POI_TABLE (reader SHAPEFILE_7)
    attributes: POI_ID long, LINK_ID long, TYPE varchar(250), POI_NAME varchar(250), ST_NAME varchar(250), LAT number(31,15), LON number(31,15)
    -> SpatialFilter_2 [Candidate]
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
Note: Zadanie 7b
CSV (reader CSV2_6)
    attributes: x x_coordinate, y y_coordinate
    -> VertexCreator_6
VertexCreator_6
    CLOSE_LINES = Yes
    IGNORE_DUPLICATES = No
    MEASURE_TYPE = Continuous
    MISSING_VAL_MODE = Compute
    MODE_NAME = Add Point
    XVAL = @Value(x)
    YVAL = @Value(y)
    -> LineBuilder_6
LineBuilder_6
    ACCUM_INPUT_ATTRS = Use Attributes From One Feature
    REMOVE_DUPLICATES = NO
    LINE -> Reprojector_14
Reprojector_14
    DEST = DHDN.Berlin/Cassini
    INTERPOLATION_TYPE_NAME = Nearest Neighbor
    RASTER_CELL_SIZE = Preserve Cells
    RASTER_TOLERANCE = 0.0
    REPROJECTED -> ShortestPathFinder_5 [FROM-TO]
T2019_KAR_STREETS (reader SHAPEFILE_9)
    attributes: LINK_ID long, ST_NAME varchar(254), REF_IN_ID long, NREF_IN_ID long, FUNC_CLASS varchar(1), SPEED_CAT varchar(1), FR_SPEED_L long, TO_SPEED_L long, DIR_TRAVEL varchar(1)
    -> Reprojector_15
Reprojector_15
    DEST = DHDN.Berlin/Cassini
    INTERPOLATION_TYPE_NAME = Nearest Neighbor
    RASTER_CELL_SIZE = Preserve Cells
    RASTER_TOLERANCE = 0.0
    SOURCE = $(SourceDataset_SHAPEFILE)
    REPROJECTED -> Tester_3
Tester_3
    BOOL_OP = OR
    TEST_CLAUSE:
      TEST @Value(DIR_TRAVEL) = B
      TEST @Value(DIR_TRAVEL) = T
    TEST_MODE = TEST
    PASSED -> AttributeCreator_5
    FAILED -> AttributeCreator_6
AttributeCreator_5
    ATTR_TABLE:
      SET_TO ForwardCost = 1
      SET_TO ReverseCost = 1
    -> ShortestPathFinder_6 [NETWORK]
AttributeCreator_6
    ATTR_TABLE:
      SET_TO ForwardCost = 1
      SET_TO ReverseCost = 9999
    -> ShortestPathFinder_6 [NETWORK]
Note: Zadanie 7a
T2019_KAR_STREETS (reader SHAPEFILE_8)
    attributes: LINK_ID long, ST_NAME varchar(254), REF_IN_ID long, NREF_IN_ID long, FUNC_CLASS varchar(1), SPEED_CAT varchar(1), FR_SPEED_L long, TO_SPEED_L long, DIR_TRAVEL varchar(1)
    -> Reprojector_17
Reprojector_17
    DEST = DHDN.Berlin/Cassini
    INTERPOLATION_TYPE_NAME = Nearest Neighbor
    RASTER_CELL_SIZE = Preserve Cells
    RASTER_TOLERANCE = 0.0
    SOURCE = $(SourceDataset_SHAPEFILE)
    REPROJECTED -> ShortestPathFinder_5 [NETWORK]
ShortestPathFinder_5
    ALLOW_UTURNS = Yes
    REORDER_MODE = NONE
    SNAP_POINTS = Yes
    SNAP_TOLERANCE = 200
    WEIGHT_ATTR_CHOICE = BY_LENGTH
    PATH -> SpatialFilter_5 [Filter]
    PATH -> LengthCalculator
LengthCalculator
    DIM = 2
    LEN_ATTR = _length
    MULT = 1
    -> StatisticsCalculator
T2019_KAR_STREET_NODE (reader SHAPEFILE_10)
    attributes: NODE_ID long, LINK_ID long, POINT_NUM long, Z_LEVEL long, INTERSECT varchar(1), LAT number(31,15), LON number(31,15)
    -> Reprojector_18
Reprojector_18
    DEST = DHDN.Berlin/Cassini
    INTERPOLATION_TYPE_NAME = Nearest Neighbor
    RASTER_CELL_SIZE = Preserve Cells
    RASTER_TOLERANCE = 0.0
    SOURCE = $(SourceDataset_SHAPEFILE)
    REPROJECTED -> SpatialFilter_3 [Candidate]
CSV (reader CSV2_7)
    attributes: x x_coordinate, y y_coordinate
    -> VertexCreator_7
VertexCreator_7
    CLOSE_LINES = Yes
    IGNORE_DUPLICATES = No
    MEASURE_TYPE = Continuous
    MISSING_VAL_MODE = Compute
    MODE_NAME = Add Point
    XVAL = @Value(x)
    YVAL = @Value(y)
    -> LineBuilder_7
LineBuilder_7
    ACCUM_INPUT_ATTRS = Use Attributes From One Feature
    REMOVE_DUPLICATES = NO
    LINE -> Reprojector_16
Reprojector_16
    DEST = DHDN.Berlin/Cassini
    INTERPOLATION_TYPE_NAME = Nearest Neighbor
    RASTER_CELL_SIZE = Preserve Cells
    RASTER_TOLERANCE = 0.0
    REPROJECTED -> ShortestPathFinder_6 [FROM-TO]
ShortestPathFinder_6
    ALLOW_UTURNS = Yes
    REORDER_MODE = NONE
    SNAP_POINTS = No
    WEIGHT_ATTR_1 = ForwardCost
    WEIGHT_ATTR_2 = ReverseCost
    WEIGHT_ATTR_CHOICE = BY_TWO_ATTRIBUTES
    PATH -> SpatialFilter_3 [Filter]
    PATH -> LengthCalculator_2
SpatialFilter_3
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> StatisticsCalculator_2
LengthCalculator_2
    DIM = 2
    LEN_ATTR = _length
    MULT = 1
    -> StatisticsCalculator_2
StatisticsCalculator_2
    CALCULATION_MODE = NUMERIC
T2019_KAR_STREET_NODE (reader SHAPEFILE_11)
    attributes: NODE_ID long, LINK_ID long, POINT_NUM long, Z_LEVEL long, INTERSECT varchar(1), LAT number(31,15), LON number(31,15)
    -> Reprojector_19
Reprojector_19
    DEST = DHDN.Berlin/Cassini
    INTERPOLATION_TYPE_NAME = Nearest Neighbor
    RASTER_CELL_SIZE = Preserve Cells
    RASTER_TOLERANCE = 0.0
    SOURCE = $(SourceDataset_SHAPEFILE)
    REPROJECTED -> SpatialFilter_5 [Candidate]
SpatialFilter_5
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> StatisticsCalculator
StatisticsCalculator
    CALCULATION_MODE = NUMERIC
